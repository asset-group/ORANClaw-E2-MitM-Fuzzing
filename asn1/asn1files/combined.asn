-- ASN1START
-- **************************************************************
--
-- Common definitions
-- Derived from 3GPP 38.413 (NGAP)
--
-- **************************************************************

E2AP-CommonDataTypes {
iso(1) identified-organization(3) dod(6) internet(1) private(4) enterprise(1) 53148 e2(1) version2 (2) e2ap(1) e2ap-CommonDataTypes (3) }

DEFINITIONS AUTOMATIC TAGS ::=

BEGIN

Criticality		::= ENUMERATED { reject, ignore, notify }

Presence		::= ENUMERATED { optional, conditional, mandatory }

ProcedureCode		::= INTEGER (0..255)

ProtocolIE-ID		::= INTEGER (0..65535)

TriggeringMessage	::= ENUMERATED { initiating-message, successful-outcome, unsuccessfull-outcome }


-- ASN1STOP

-- ASN1START
-- **************************************************************
--
-- Constant definitions
--
-- **************************************************************
-- **************************************************************
--
-- Elementary Procedures
--
-- **************************************************************
id-E2setup									ProcedureCode ::= 1
id-ErrorIndication							ProcedureCode ::= 2
id-Reset									ProcedureCode ::= 3
id-RICcontrol								ProcedureCode ::= 4
id-RICindication							ProcedureCode ::= 5
id-RICserviceQuery							ProcedureCode ::= 6
id-RICserviceUpdate							ProcedureCode ::= 7
id-RICsubscription							ProcedureCode ::= 8
id-RICsubscriptionDelete					ProcedureCode ::= 9
id-E2nodeConfigurationUpdate				ProcedureCode ::= 10
id-E2connectionUpdate						ProcedureCode ::= 11
id-RICsubscriptionDeleteRequired			ProcedureCode ::= 12
id-E2removal								ProcedureCode ::= 13
id-RICsubscriptionModification				ProcedureCode ::= 14
id-RICsubscriptionModificationRequired		ProcedureCode ::= 15
id-RICquery									ProcedureCode ::= 16

-- **************************************************************
--
-- Extension constants
--
-- **************************************************************

maxProtocolIEs								INTEGER ::= 65535


-- **************************************************************
--
-- Lists
--
-- **************************************************************
maxnoofErrors								INTEGER ::= 256
maxofE2nodeComponents						INTEGER ::= 1024
maxofRANfunctionID							INTEGER ::= 256
maxofRICactionID							INTEGER ::= 16
maxofTNLA									INTEGER ::= 32
maxofRICrequestID							INTEGER ::= 1024


-- **************************************************************
--
-- IEs
--
-- **************************************************************
id-Cause											ProtocolIE-ID ::= 1
id-CriticalityDiagnostics							ProtocolIE-ID ::= 2
id-GlobalE2node-ID									ProtocolIE-ID ::= 3
id-GlobalRIC-ID										ProtocolIE-ID ::= 4
id-RANfunctionID									ProtocolIE-ID ::= 5
id-RANfunctionID-Item								ProtocolIE-ID ::= 6
id-RANfunctionIEcause-Item							ProtocolIE-ID ::= 7
id-RANfunction-Item									ProtocolIE-ID ::= 8
id-RANfunctionsAccepted								ProtocolIE-ID ::= 9
id-RANfunctionsAdded								ProtocolIE-ID ::= 10
id-RANfunctionsDeleted								ProtocolIE-ID ::= 11
id-RANfunctionsModified								ProtocolIE-ID ::= 12
id-RANfunctionsRejected								ProtocolIE-ID ::= 13
id-RICaction-Admitted-Item							ProtocolIE-ID ::= 14
id-RICactionID										ProtocolIE-ID ::= 15
id-RICaction-NotAdmitted-Item						ProtocolIE-ID ::= 16
id-RICactions-Admitted								ProtocolIE-ID ::= 17
id-RICactions-NotAdmitted							ProtocolIE-ID ::= 18
id-RICaction-ToBeSetup-Item							ProtocolIE-ID ::= 19
id-RICcallProcessID									ProtocolIE-ID ::= 20
id-RICcontrolAckRequest								ProtocolIE-ID ::= 21
id-RICcontrolHeader									ProtocolIE-ID ::= 22
id-RICcontrolMessage								ProtocolIE-ID ::= 23
id-RICcontrolStatus									ProtocolIE-ID ::= 24
id-RICindicationHeader								ProtocolIE-ID ::= 25
id-RICindicationMessage								ProtocolIE-ID ::= 26
id-RICindicationSN									ProtocolIE-ID ::= 27
id-RICindicationType								ProtocolIE-ID ::= 28
id-RICrequestID										ProtocolIE-ID ::= 29
id-RICsubscriptionDetails							ProtocolIE-ID ::= 30
id-TimeToWait										ProtocolIE-ID ::= 31
id-RICcontrolOutcome								ProtocolIE-ID ::= 32
id-E2nodeComponentConfigUpdate						ProtocolIE-ID ::= 33
id-E2nodeComponentConfigUpdate-Item					ProtocolIE-ID ::= 34
id-E2nodeComponentConfigUpdateAck					ProtocolIE-ID ::= 35
id-E2nodeComponentConfigUpdateAck-Item				ProtocolIE-ID ::= 36
id-E2connectionSetup								ProtocolIE-ID ::= 39
id-E2connectionSetupFailed							ProtocolIE-ID ::= 40
id-E2connectionSetupFailed-Item						ProtocolIE-ID ::= 41
id-E2connectionFailed-Item							ProtocolIE-ID ::= 42
id-E2connectionUpdate-Item							ProtocolIE-ID ::= 43
id-E2connectionUpdateAdd							ProtocolIE-ID ::= 44
id-E2connectionUpdateModify							ProtocolIE-ID ::= 45
id-E2connectionUpdateRemove							ProtocolIE-ID ::= 46
id-E2connectionUpdateRemove-Item					ProtocolIE-ID ::= 47
id-TNLinformation									ProtocolIE-ID ::= 48
id-TransactionID									ProtocolIE-ID ::= 49
id-E2nodeComponentConfigAddition					ProtocolIE-ID ::= 50
id-E2nodeComponentConfigAddition-Item				ProtocolIE-ID ::= 51
id-E2nodeComponentConfigAdditionAck					ProtocolIE-ID ::= 52
id-E2nodeComponentConfigAdditionAck-Item			ProtocolIE-ID ::= 53
id-E2nodeComponentConfigRemoval						ProtocolIE-ID ::= 54
id-E2nodeComponentConfigRemoval-Item				ProtocolIE-ID ::= 55
id-E2nodeComponentConfigRemovalAck					ProtocolIE-ID ::= 56
id-E2nodeComponentConfigRemovalAck-Item				ProtocolIE-ID ::= 57
id-E2nodeTNLassociationRemoval						ProtocolIE-ID ::= 58
id-E2nodeTNLassociationRemoval-Item					ProtocolIE-ID ::= 59
id-RICsubscriptionToBeRemoved						ProtocolIE-ID ::= 60
id-RICsubscription-withCause-Item					ProtocolIE-ID ::= 61
id-RICsubscriptionStartTime							ProtocolIE-ID ::= 62
id-RICsubscriptionEndTime							ProtocolIE-ID ::= 63
id-RICeventTriggerDefinitionToBeModified			ProtocolIE-ID ::= 64
id-RICactionsToBeRemovedForModification-List		ProtocolIE-ID ::= 65
id-RICaction-ToBeRemovedForModification-Item		ProtocolIE-ID ::= 66
id-RICactionsToBeModifiedForModification-List		ProtocolIE-ID ::= 67
id-RICaction-ToBeModifiedForModification-Item		ProtocolIE-ID ::= 68
id-RICactionsToBeAddedForModification-List			ProtocolIE-ID ::= 69
id-RICaction-ToBeAddedForModification-Item			ProtocolIE-ID ::= 70
id-RICactionsRemovedForModification-List			ProtocolIE-ID ::= 71
id-RICaction-RemovedForModification-Item			ProtocolIE-ID ::= 72
id-RICactionsFailedToBeRemovedForModification-List	ProtocolIE-ID ::= 73
id-RICaction-FailedToBeRemovedForModification-Item	ProtocolIE-ID ::= 74
id-RICactionsModifiedForModification-List			ProtocolIE-ID ::= 75
id-RICaction-ModifiedForModification-Item			ProtocolIE-ID ::= 76
id-RICactionsFailedToBeModifiedForModification-List	ProtocolIE-ID ::= 77
id-RICaction-FailedToBeModifiedForModification-Item	ProtocolIE-ID ::= 78
id-RICactionsAddedForModification-List				ProtocolIE-ID ::= 79
id-RICaction-AddedForModification-Item				ProtocolIE-ID ::= 80
id-RICactionsFailedToBeAddedForModification-List	ProtocolIE-ID ::= 81
id-RICaction-FailedToBeAddedForModification-Item	ProtocolIE-ID ::= 82
id-RICactionsRequiredToBeModified-List				ProtocolIE-ID ::= 83
id-RICaction-RequiredToBeModified-Item				ProtocolIE-ID ::= 84
id-RICactionsRequiredToBeRemoved-List				ProtocolIE-ID ::= 85
id-RICaction-RequiredToBeRemoved-Item				ProtocolIE-ID ::= 86
id-RICactionsConfirmedForModification-List			ProtocolIE-ID ::= 87
id-RICaction-ConfirmedForModification-Item			ProtocolIE-ID ::= 88
id-RICactionsRefusedToBeModified-List				ProtocolIE-ID ::= 89
id-RICaction-RefusedToBeModified-Item				ProtocolIE-ID ::= 90
id-RICactionsConfirmedForRemoval-List				ProtocolIE-ID ::= 91
id-RICaction-ConfirmedForRemoval-Item				ProtocolIE-ID ::= 92
id-RICactionsRefusedToBeRemoved-List				ProtocolIE-ID ::= 93
id-RICaction-RefusedToBeRemoved-Item				ProtocolIE-ID ::= 94
id-RICqueryHeader									ProtocolIE-ID ::= 95
id-RICqueryDefinition								ProtocolIE-ID ::= 96
id-RICqueryOutcome									ProtocolIE-ID ::= 97
END
-- ASN1STOP
